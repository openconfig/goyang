module deviate {
    prefix "d";
    namespace "urn:d";

    grouping substmts {
        leaf config {
            type string;
            config true;
        }
        leaf default {
            type string;
            default "fish";
        }
        leaf mandatory {
            type string;
            mandatory false;
        }
        leaf-list max-elements {
            type string;
            max-elements 1000;
        }
        leaf-list min-elements {
            type string;
            min-elements 1000;
        }
        leaf-list max-and-min-elements {
            type string;
            max-elements 1024;
            min-elements 1;
        }
        leaf type {
            type string;
        }
        // TODO(robjs): unique for deviation
        leaf units {
            type uint16;
            units "nanofish per millenium";
        }
    }

    container target {
        container delete {
            uses substmts;
        }
    }

    deviation /target/delete/config {
        deviate delete {
            config true;
        }
    }

    deviation /target/delete/default {
        deviate delete {
            default "fish";
        }
    }

    deviation /target/delete/mandatory {
        deviate delete {
            mandatory false;
        }
    }

    deviation /target/delete/min-elements {
        deviate delete {
            min-elements 1000;
        }
    }

    deviation /target/delete/max-elements {
        deviate delete {
            max-elements 1000;
        }
    }

    deviation /target/delete/max-and-min-elements {
        deviate delete {
            max-elements 1024;
            min-elements 1;
        }
    }

    deviation /target/delete/units {
        deviate delete {
            units "nanofish per millenium";
        }
    }
}
