// Copyright 2025 Swisscom (Schweiz) AG
//
// Licensed under the Apache License, Version 2.0 (the "License");
// you may not use this file except in compliance with the License.
// You may obtain a copy of the License at
//
//     http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.

submodule presence-tests {
  belongs-to base { prefix "sbase"; }

  // sample presence
  container presence-example-container {
    presence "the presence of this container means something";
  }

  grouping grouping-no-presence {
    container container-no-presence {}
  }

  container container-with-presence {
    uses grouping-no-presence {
        refine container-no-presence {
            presence "this presence was added with a refine";
        }
    }
  }


}
