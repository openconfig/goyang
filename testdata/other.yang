// Copyright 2015 Google Inc.
//
// Licensed under the Apache License, Version 2.0 (the "License");
// you may not use this file except in compliance with the License.
// You may obtain a copy of the License at
//
//     http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.

// imported by base.yang.
module other {
  namespace "uri:empty";
  prefix "otherp";
  typedef other-type { type string; }

  // This container should not appear in base, even though this file is
  // imported by base.  That is just the YANG is defined.
  container other-container {
    leaf other-container-leaf1 { type other-type; }
    leaf other-container-leaf2 { type otherp:other-type; }
  }
  grouping other-group {
    leaf other-group-leaf { type string; }
  }
}
