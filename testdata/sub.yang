// Copyright 2015 Google Inc.
//
// Licensed under the Apache License, Version 2.0 (the "License");
// you may not use this file except in compliance with the License.
// You may obtain a copy of the License at
//
//     http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.

// included by base.yang.
submodule sub {
  belongs-to base { prefix "sbase"; }
  typedef sub-type { type sub-type2; }
  typedef sub-type2 { type int8; }
  container sub-container {
    leaf sub-container-leaf { type sub-type; }
  }
  grouping sub-group {
    leaf sub-group-leaf { type string; }
  }
}
