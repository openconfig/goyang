// Copyright 2025 Swisscom (Schweiz) AG
//
// Licensed under the Apache License, Version 2.0 (the "License");
// you may not use this file except in compliance with the License.
// You may obtain a copy of the License at
//
//     http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.

submodule refine-tests {
  belongs-to base { prefix "sbase"; }
  grouping refine-sub-group {
    leaf refine-sub-group-leaf {
        type string;
        default "initial-default";
        }
  }

  // sample refine description
  container refine-description {
    uses refine-sub-group {
      refine "refine-sub-group-leaf" {
        description "new refined description";
      }
    }
  }

  // sample refine leaf default
  container refine-default {
    uses refine-sub-group {
      refine refine-sub-group-leaf {
        default "refined-default-string";
      }
    }
  }

  grouping fruit-bowl {
    description
      "A bowl with a few pieces of fruit by default.";
    leaf-list fruit {
      type string;
      default "apple";
      default "banana";
    }
  }

  // sample refine leaf-list defaults
  container exotic-bowl {
    uses fruit-bowl {
      refine fruit {
        default "mango";
        default "papaya";
      }
    }
  }

}
